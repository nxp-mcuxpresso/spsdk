-- Definition derived from openssl 3.0

OSCCA DEFINITIONS ::= BEGIN

    Signature ::= SEQUENCE {
        r       INTEGER,
        s       INTEGER
    }

    KeySet ::= SEQUENCE {
        number  INTEGER,
        prk     OCTET STRING,
        puk     [1] EXPLICIT BIT STRING
    }

    Private ::= SEQUENCE {
        number      INTEGER,
        ids         SEQUENCE OF OBJECT IDENTIFIER,
        keyset      OCTET STRING
    }

    Public ::= SEQUENCE {
        ids     SEQUENCE OF OBJECT IDENTIFIER,
        puk     BIT STRING
    }

END
